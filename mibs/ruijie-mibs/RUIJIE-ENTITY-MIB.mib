-- *****************************************************************
-- RUIJIE-ENTITY-MIB.mib:  Ruijie Entity MIB file
--
-- March 2002, Wuzg
--
-- Copyright (c) 2002 by Ruijie Networks Co.,Ltd.
-- All rights reserved.
-- 
-- *****************************************************************
--

RUIJIE-ENTITY-MIB DEFINITIONS ::= BEGIN

IMPORTS
        MODULE-IDENTITY,
        OBJECT-TYPE,
        NOTIFICATION-TYPE,
        Integer32
                FROM SNMPv2-SMI
        DisplayString,
        MacAddress
                FROM SNMPv2-TC
        MODULE-COMPLIANCE,
        OBJECT-GROUP,
        NOTIFICATION-GROUP
                FROM SNMPv2-CONF
        ruijieMgmt
                FROM RUIJIE-SMI;

ruijieEntityMIB MODULE-IDENTITY
	LAST-UPDATED "200203200000Z"
	ORGANIZATION "Ruijie Networks Co.,Ltd."
	CONTACT-INFO
        " 
		    Tel: 4008-111-000 

		    E-mail: service@ruijie.com.cn"
	DESCRIPTION
		"This module defines ruijie entity mibs."
	REVISION      "200203200000Z"
	DESCRIPTION
		"Initial version of this MIB module."
	::= { ruijieMgmt 21}

ruijieDeviceMIBObjects OBJECT IDENTIFIER ::= { ruijieEntityMIB 1 }


--
-- device information
--
ruijieDeviceMaxNumber OBJECT-TYPE
          SYNTAX Integer32
          MAX-ACCESS read-only
          STATUS current
          DESCRIPTION
              "Max number of devices of the system permitting."
          ::= { ruijieDeviceMIBObjects 1 }
        
ruijieDeviceInfoTable OBJECT-TYPE
        SYNTAX SEQUENCE OF RuijieDeviceInfoEntry
        MAX-ACCESS not-accessible
        STATUS current
        DESCRIPTION
            "List of devices."
        ::= { ruijieDeviceMIBObjects 2 }
        
ruijieDeviceInfoEntry OBJECT-TYPE
        SYNTAX RuijieDeviceInfoEntry
        MAX-ACCESS not-accessible
        STATUS current
        DESCRIPTION
            "Entry of a device information."
        INDEX { ruijieDeviceInfoIndex }
        ::= { ruijieDeviceInfoTable 1 }
    
RuijieDeviceInfoEntry ::=
        SEQUENCE {
	       ruijieDeviceInfoIndex Integer32,
	       ruijieDeviceInfoDescr DisplayString,
	       ruijieDeviceInfoSlotNumber Integer32,
               ruijieDevicePowerStatus  INTEGER,
	       ruijieDeviceMacAddress MacAddress,
               ruijieDevicePriority Integer32,
               ruijieDeviceAlias  DisplayString,
               ruijieDeviceSWVersion DisplayString,
               ruijieDeviceHWVersion DisplayString,
	       ruijieDeviceSerialNumber DisplayString 
        }
        
ruijieDeviceInfoIndex OBJECT-TYPE
        SYNTAX Integer32
        MAX-ACCESS read-only
        STATUS current
        DESCRIPTION
            "An unique value of each devices in system. Its value ranges between
            1 and the value of the object ruijieDeviceNumber."
        ::= { ruijieDeviceInfoEntry 1 }
              
ruijieDeviceInfoDescr OBJECT-TYPE
        SYNTAX DisplayString (SIZE(0..32))
        MAX-ACCESS read-only
        STATUS current
        DESCRIPTION
            "Description of the device."
        ::= { ruijieDeviceInfoEntry 2 }
        
ruijieDeviceInfoSlotNumber OBJECT-TYPE
        SYNTAX Integer32
        MAX-ACCESS read-only
        STATUS current
        DESCRIPTION
            "The number of slots exists on the device."
        ::= { ruijieDeviceInfoEntry 3 }
        
          
ruijieDevicePowerStatus OBJECT-TYPE
          SYNTAX  INTEGER {
                    rpsNoLink   (1), -- no rps link or rps not electrifying,
                    rpsLinkAndNoPower (2), -- rps linked but not electrifying,
                    rpsLinkAndReadyForPower (3), -- rps is ready for power,
                    rpsLinkAndPower (4)  -- rps is serving as a power
                }
          MAX-ACCESS read-only
          STATUS current
          DESCRIPTION
              "The power status of device"
          ::= { ruijieDeviceInfoEntry 4 }
        
ruijieDeviceMacAddress OBJECT-TYPE
          SYNTAX  MacAddress
          MAX-ACCESS read-only
          STATUS current
          DESCRIPTION
              "The physical address of device"
          ::= { ruijieDeviceInfoEntry 5 }

ruijieDevicePriority OBJECT-TYPE
          SYNTAX  Integer32(1..10)
          MAX-ACCESS read-write
          STATUS current
          DESCRIPTION
              "The device priority value"
          ::= { ruijieDeviceInfoEntry 6 }
          
ruijieDeviceAlias OBJECT-TYPE
        SYNTAX DisplayString (SIZE(0..32))
        MAX-ACCESS read-write
        STATUS current
        DESCRIPTION
            "Alias of the device."
        ::= { ruijieDeviceInfoEntry 7 }     


ruijieDeviceSWVersion OBJECT-TYPE
        SYNTAX DisplayString (SIZE(1..32))
        MAX-ACCESS read-only
        STATUS current
        DESCRIPTION
            "Description of the device."
        ::= { ruijieDeviceInfoEntry 8 }
        
ruijieDeviceHWVersion OBJECT-TYPE
        SYNTAX DisplayString (SIZE(1..32))
        MAX-ACCESS read-only
        STATUS current
        DESCRIPTION
            "Description of the device."
        ::= { ruijieDeviceInfoEntry 9 }  

ruijieDeviceSerialNumber OBJECT-TYPE
        SYNTAX DisplayString (SIZE(1..32))
        MAX-ACCESS read-only
        STATUS current
        DESCRIPTION
            "Serial number of the device."
        ::= { ruijieDeviceInfoEntry 10 }
       
--
-- module information  
--
--ruijieModuleNumber OBJECT-TYPE
--        SYNTAX Integer32
--        MAX-ACCESS read-only
--        STATUS current
--        DESCRIPTION
--            "Current number of modules in the system."
--        ::= { ruijieDeviceMIBObjects 2 }

ruijieSlotInfoTable OBJECT-TYPE
        SYNTAX SEQUENCE OF RuijieSlotInfoEntry
        MAX-ACCESS not-accessible
        STATUS current
        DESCRIPTION
            "a list of module Entries."
        ::= { ruijieDeviceMIBObjects 3 }
    
ruijieSlotInfoEntry OBJECT-TYPE
        SYNTAX RuijieSlotInfoEntry
        MAX-ACCESS not-accessible
        STATUS current
        DESCRIPTION
            "Entry containing status information about one slot."
        INDEX { ruijieSlotInfoDeviceIndex, ruijieSlotInfoIndex }
        ::= { ruijieSlotInfoTable 1 }

RuijieSlotInfoEntry ::= 
        SEQUENCE {
             ruijieSlotInfoDeviceIndex Integer32,
             ruijieSlotInfoIndex Integer32,
             ruijieSlotModuleInfoDescr DisplayString,
             ruijieSlotInfoPortNumber Integer32,
             ruijieSlotInfoPortMaxNumber Integer32,
             ruijieSlotInfoDesc  DisplayString,
             ruijieSlotConfigModuleInfoDescr DisplayString,
             ruijieSlotUserStatus Integer32,
             ruijieSlotSoftwareStatus Integer32,
             ruijieSlotSerialNumber DisplayString,
             ruijieSlotHWVersion DisplayString
        }
    
ruijieSlotInfoDeviceIndex OBJECT-TYPE
        SYNTAX Integer32
        MAX-ACCESS read-only
        STATUS current
        DESCRIPTION
            "The index of the device, that the slot exists on."
        ::= { ruijieSlotInfoEntry 1 }
    
ruijieSlotInfoIndex OBJECT-TYPE
        SYNTAX Integer32
        MAX-ACCESS read-only
        STATUS current
        DESCRIPTION
            "A unique value for each slot exist on the device specified by
            the field ruijieSlotInfoDeviceIndex, Its value ranges
            between 1 and the value of the solt num  of this device."
        ::= { ruijieSlotInfoEntry 2 }
    
ruijieSlotModuleInfoDescr OBJECT-TYPE
        SYNTAX DisplayString
        MAX-ACCESS read-only
        STATUS current
        DESCRIPTION
            "Descriptions for the module in the Slot. just like 's1902m' etc. It is a 
             unique value for identifing a kind of module.This value will be null string
             if slot is empty is NULL"
        ::= { ruijieSlotInfoEntry 3 }
    
ruijieSlotInfoPortNumber OBJECT-TYPE
        SYNTAX Integer32
        MAX-ACCESS read-only
        STATUS current
        DESCRIPTION
            "Number of ports on this slot.This value will be 0  if slot is empty"
        ::= { ruijieSlotInfoEntry 4 }

ruijieSlotInfoPortMaxNumber OBJECT-TYPE
        SYNTAX Integer32
        MAX-ACCESS read-only
        STATUS current
        DESCRIPTION
            "Max number of ports on this slot has possibly."
        ::= { ruijieSlotInfoEntry 5 }
                      
ruijieSlotInfoDesc OBJECT-TYPE
        SYNTAX  DisplayString(SIZE(0..32))
        MAX-ACCESS read-only
        STATUS current
        DESCRIPTION
            "Description of the slot,the same as the pannel show."
        ::= { ruijieSlotInfoEntry 6 }
        
ruijieSlotConfigModuleInfoDescr OBJECT-TYPE
        SYNTAX  DisplayString(SIZE(0..32))
        MAX-ACCESS read-only
        STATUS current
        DESCRIPTION
            "Description of the configured module name on the slot, such as 'M8600-48GT/4SFP','NMX-8E1/CE1H',etc.
            This value will be 'none' if module on the slot isn't configured, or 'N/A' if not allowed to configure."
        ::= { ruijieSlotInfoEntry 7 }        
        
ruijieSlotUserStatus OBJECT-TYPE
        SYNTAX Integer32
        MAX-ACCESS read-only
        STATUS current
        DESCRIPTION
            "User status of the slot.
	             value      status          	description
			     0          NONE  	  			not configured(for linecard)
			     1          INSTALLED 			configured to install(for linecard)
			     2          UNINSTALLED			configured to uninstall(for linecard)
			     3          NA             		not allowed to configure(for mainboard or Cassette switch)
            "
        ::= { ruijieSlotInfoEntry 8 }
        
ruijieSlotSoftwareStatus OBJECT-TYPE
        SYNTAX Integer32
        MAX-ACCESS read-only
        STATUS current
        DESCRIPTION
            "Software status of the slot.
	            value       status          		description
				0			NONE            		not running(for all)
				1			OK              		running(for linecard or Cassette switch)
				2			CONFLICT        		confilct with installed module(for linecard)  
				3			REMOVED					module removed(for linecard)
				4			VERSION_IMCOMPATIBLE	version error(for linecard)
				5			CANNOT_STARTUP			can not start(for linecard)
				6			RESETTING				restarting(for linecard)
				7			MASTER            		master board(for mainboard)
				8			BACKUP            		slave board(for mainboard)            
            "
        ::= { ruijieSlotInfoEntry 9 } 

ruijieSlotSerialNumber OBJECT-TYPE
        SYNTAX  DisplayString(SIZE(0..32))
        MAX-ACCESS read-only
        STATUS current
        DESCRIPTION
            "Serial number of the module in the Slot."
        ::= { ruijieSlotInfoEntry 10 }
 
ruijieSlotHWVersion OBJECT-TYPE
        SYNTAX DisplayString (SIZE(1..32))
        MAX-ACCESS read-only
        STATUS current
        DESCRIPTION
            "Description of the slot."
        ::= { ruijieSlotInfoEntry 11 }

--
--ModuleTempState
--          
ruijieModuleTempStateTable OBJECT-TYPE
        SYNTAX SEQUENCE OF RuijieModuleTempStateEntry
        MAX-ACCESS not-accessible
        STATUS current
        DESCRIPTION
            "Table of entrance to module temperature state table."
        ::= { ruijieDeviceMIBObjects 4 }
    
ruijieModuleTempStateEntry OBJECT-TYPE
        SYNTAX RuijieModuleTempStateEntry
        MAX-ACCESS not-accessible
        STATUS current
        DESCRIPTION
            "Entrance to module temperature state." 
        INDEX { ruijieModuleTempStateDeviceIndex, ruijieModuleTempStateIndex }
        ::= { ruijieModuleTempStateTable 1 }

RuijieModuleTempStateEntry ::= 
        SEQUENCE {
	     ruijieModuleTempStateDeviceIndex Integer32, 
             ruijieModuleTempStateIndex Integer32,
             ruijieModuleTempState  INTEGER
        }

ruijieModuleTempStateDeviceIndex OBJECT-TYPE
        SYNTAX Integer32
        MAX-ACCESS read-only
        STATUS current
        DESCRIPTION
            "The index number for the device which the module is in." 
        ::= { ruijieModuleTempStateEntry 1 }
  
ruijieModuleTempStateIndex OBJECT-TYPE
        SYNTAX Integer32
        MAX-ACCESS read-only
        STATUS current
        DESCRIPTION
            " The module index number, ranging from 1 to the maximal slot number." 
        ::= { ruijieModuleTempStateEntry 2 }
    
ruijieModuleTempState OBJECT-TYPE
        SYNTAX INTEGER{
        	tempNormal(1),
        	tempWarning(2)
        }
        MAX-ACCESS read-only
        STATUS current
        DESCRIPTION
            " The module temperature state." 
        ::= { ruijieModuleTempStateEntry 3 }

ruijiePowerStateTable OBJECT-TYPE
        SYNTAX SEQUENCE OF RuijiePowerStateEntry
        MAX-ACCESS not-accessible
        STATUS current
        DESCRIPTION
            "Table of entrance to the power state." 
        ::= { ruijieDeviceMIBObjects 5 }
    
ruijiePowerStateEntry OBJECT-TYPE
        SYNTAX RuijiePowerStateEntry
        MAX-ACCESS not-accessible
        STATUS current
        DESCRIPTION
            "Entrance to the power state." 
        INDEX { ruijiePowerStateDeviceIndex, ruijiePowerStateIndex }
        ::= { ruijiePowerStateTable 1 }

RuijiePowerStateEntry ::= 
        SEQUENCE {
	     ruijiePowerStateDeviceIndex Integer32,
             ruijiePowerStateIndex Integer32,
             ruijiePowerState  INTEGER,
             ruijiePowerStatePowerDescr  DisplayString
        }

ruijiePowerStateDeviceIndex OBJECT-TYPE
        SYNTAX Integer32
        MAX-ACCESS read-only
        STATUS current
        DESCRIPTION
             "The index number for the device which the power is in." 
        ::= { ruijiePowerStateEntry 1 }
    
ruijiePowerStateIndex OBJECT-TYPE
        SYNTAX Integer32
        MAX-ACCESS read-only
        STATUS current
        DESCRIPTION
            "The power index number."
        ::= { ruijiePowerStateEntry 2 }
    
ruijiePowerState OBJECT-TYPE
        SYNTAX INTEGER{
        	noLink(1),                 --no exist
        	linkAndNoPower(2),         --exist but no power
        	linkAndReadyForPower(3),   --exist and ready for power
        	linkAndPower(4),           --normal power 
		linkAndPowerAbnormal(5)    --power,but abnormal at fan
        }
        MAX-ACCESS read-only
        STATUS current
        DESCRIPTION
            "Power state."
        ::= { ruijiePowerStateEntry 3 }

ruijiePowerStatePowerDescr OBJECT-TYPE
        SYNTAX DisplayString (SIZE(0..32))
        MAX-ACCESS read-only
        STATUS current
        DESCRIPTION
            "Description of the power."
        ::= { ruijiePowerStateEntry 4 }

ruijieFanStateTable OBJECT-TYPE
        SYNTAX SEQUENCE OF RuijieFanStateEntry
        MAX-ACCESS not-accessible
        STATUS current
        DESCRIPTION
            "Table of entrance to the fan state." 
        ::= { ruijieDeviceMIBObjects 6 }
    
ruijieFanStateEntry OBJECT-TYPE
        SYNTAX RuijieFanStateEntry
        MAX-ACCESS not-accessible
        STATUS current
        DESCRIPTION
            "Entrance to the fan state."
        INDEX {  ruijieFanStateDeviceIndex, ruijieFanStateIndex }
        ::= { ruijieFanStateTable 1 }

RuijieFanStateEntry ::= 
        SEQUENCE {
	     ruijieFanStateDeviceIndex Integer32,
             ruijieFanStateIndex Integer32,
             ruijieFanState  INTEGER,
             ruijieFanStateFanDescr  DisplayString
        }

ruijieFanStateDeviceIndex OBJECT-TYPE
        SYNTAX Integer32
        MAX-ACCESS read-only
        STATUS current
        DESCRIPTION
            "The index number for the device which the fan is in."
        ::= { ruijieFanStateEntry 1 }
    
ruijieFanStateIndex OBJECT-TYPE
        SYNTAX Integer32
        MAX-ACCESS read-only
        STATUS current
        DESCRIPTION
            "Fan index number."  
        ::= { ruijieFanStateEntry 2 }
    
ruijieFanState OBJECT-TYPE
        SYNTAX INTEGER{
        	work(1),      --fan working
        	stop(2)      --fan stopping or no exist 
        }
        MAX-ACCESS read-only
        STATUS current
        DESCRIPTION
            "Fan state."  
        ::= { ruijieFanStateEntry 3 }
           
ruijieFanStateFanDescr OBJECT-TYPE
        SYNTAX DisplayString (SIZE(0..32))
        MAX-ACCESS read-only
        STATUS current
        DESCRIPTION
            "Description of the fan."
        ::= { ruijieFanStateEntry 4 }
           

ruijieEntityMIBTraps OBJECT IDENTIFIER ::= { ruijieEntityMIB 2 }      

ruijieEntityStateChgDesc OBJECT-TYPE
        SYNTAX DisplayString
        MAX-ACCESS accessible-for-notify
        STATUS current
        DESCRIPTION
          "The description of entity change."
        ::= { ruijieEntityMIBTraps 1 }       
        
ruijieEntityStatusChange NOTIFICATION-TYPE
        OBJECTS   {ruijieEntityStateChgDesc}
        STATUS     current
        DESCRIPTION
                "while status of the entity changed, then this trap will be sent."
        ::= { ruijieEntityMIBTraps 2 }                    
        
ruijieTemperatureWarningDesc OBJECT-TYPE
        SYNTAX DisplayString (SIZE(0..255))
        MAX-ACCESS accessible-for-notify
        STATUS current
        DESCRIPTION
          "Description on the temperature state changes." 
        ::= { ruijieEntityMIBTraps 3 }       
        
ruijieTemperatureWarning NOTIFICATION-TYPE
        OBJECTS   { ruijieTemperatureWarningDesc }
        STATUS     current
        DESCRIPTION
            " When the temperature state of this module changes, this Trap will be sent." 
        ::= { ruijieEntityMIBTraps 4 }
        
        
-- conformance information

ruijieDeviceMIBConformance OBJECT IDENTIFIER ::= { ruijieEntityMIB 3 }
ruijieDeviceMIBCompliances OBJECT IDENTIFIER ::= { ruijieDeviceMIBConformance 1 }
ruijieDeviceMIBGroups      OBJECT IDENTIFIER ::= { ruijieDeviceMIBConformance 2 }


-- compliance statements

ruijieDeviceMIBCompliance MODULE-COMPLIANCE
        STATUS  current
        DESCRIPTION
                "The compliance statement for entities which implement
                the Ruijie Device MIB"
        MODULE  -- this module
                MANDATORY-GROUPS { ruijieDeviceInfoMIBGroup,
                                   ruijieModuleInfoMIBGroup
                 }
                 GROUP      ruijieOptionalDevInfoMIBGroup
                 DESCRIPTION
                     "This group is optional for those system which support device priority,alias and macaddress 
                      information"  
                 
                 GROUP      ruijieEntityChgDescGroup
                 DESCRIPTION
                     "This group is mandatory only for those system which support entity
                     change notification."  
                                      
                GROUP       ruijieDeviceMIBNotificationGroup
                DESCRIPTION
                     "This group is mandatory only for those system which support entity
                     change notification."  
                      
                GROUP   ruijieModuleTempStateGroup
		DESCRIPTION  
                     "This group is mandatory when the system supports temperature state detection."   

                GROUP   ruijiePowerStateGroup
		DESCRIPTION  
                      "This group is mandatory when the system supports power state identification." 

                GROUP   ruijieFanStateGroup
		DESCRIPTION  
                     "This group is mandatory when the system supports fan state identification." 
  
		GROUP  ruijieTemperatureWarningDescGroup 
		DESCRIPTION
                      "This group is mandatory when the system supports temperature state notification." 

                GROUP   ruijieTemperatureWarningGroup
                DESCRIPTION 
                      "This group is mandatory when the system supports temperature state notification." 

        ::= { ruijieDeviceMIBCompliances 1 }
                
-- units of conformance

ruijieDeviceInfoMIBGroup OBJECT-GROUP
        OBJECTS {
          ruijieDeviceMaxNumber, 
	       ruijieDeviceInfoIndex,
	       ruijieDeviceInfoDescr,
	       ruijieDeviceInfoSlotNumber,
	       ruijieDevicePowerStatus
        }
        STATUS  current
        DESCRIPTION
                "A collection of objects providing device information to a
                Ruijie agent."
        ::= { ruijieDeviceMIBGroups 1 } 

ruijieOptionalDevInfoMIBGroup OBJECT-GROUP
        OBJECTS {
	       ruijieDeviceMacAddress,
	       ruijieDevicePriority,
	       ruijieDeviceAlias,
               ruijieDeviceSWVersion,
               ruijieDeviceHWVersion,
               ruijieDeviceSerialNumber
        }
        STATUS  current
        DESCRIPTION
                "A collection of objects providing optional device information to a
                Ruijie agent."
        ::= { ruijieDeviceMIBGroups 2 } 
        
ruijieModuleInfoMIBGroup OBJECT-GROUP
        OBJECTS {
             ruijieSlotInfoDeviceIndex,
             ruijieSlotInfoIndex,
             ruijieSlotModuleInfoDescr,
             ruijieSlotInfoPortNumber,
             ruijieSlotInfoPortMaxNumber,
	     ruijieSlotInfoDesc, 
             ruijieSlotConfigModuleInfoDescr,
             ruijieSlotUserStatus,
             ruijieSlotSoftwareStatus,
	     ruijieSlotSerialNumber,
	     ruijieSlotHWVersion
        }
        STATUS  current
        DESCRIPTION
                "A collection of objects providing module information to a
                Ruijie agent."
        ::= { ruijieDeviceMIBGroups 3 }                
                               
ruijieEntityChgDescGroup OBJECT-GROUP
        OBJECTS {ruijieEntityStateChgDesc}
        STATUS  current
        DESCRIPTION
                "Objects that providing a literal description of entity's change."
        ::= { ruijieDeviceMIBGroups 4 }             
        
ruijieDeviceMIBNotificationGroup NOTIFICATION-GROUP
    NOTIFICATIONS {ruijieEntityStatusChange}
    STATUS        current
    DESCRIPTION
            "The collection of notifications which used to inform entity general status information"
    ::= { ruijieDeviceMIBGroups 5}

ruijieModuleTempStateGroup OBJECT-GROUP
        OBJECTS {
	     ruijieModuleTempStateDeviceIndex, 
             ruijieModuleTempStateIndex,
             ruijieModuleTempState
		}
        STATUS  current
        DESCRIPTION
                "Collection of information on temperature state."
        ::= { ruijieDeviceMIBGroups 6 }             

ruijiePowerStateGroup OBJECT-GROUP
        OBJECTS {
	     ruijiePowerStateDeviceIndex,
             ruijiePowerStateIndex,
             ruijiePowerState,
             ruijiePowerStatePowerDescr
		}
        STATUS  current
        DESCRIPTION
                 "Collection of information on power state." 
        ::= { ruijieDeviceMIBGroups 7 } 
            
ruijieFanStateGroup OBJECT-GROUP
        OBJECTS {
	     ruijieFanStateDeviceIndex,
             ruijieFanStateIndex,
             ruijieFanState,
             ruijieFanStateFanDescr
		}
        STATUS  current
        DESCRIPTION
                 "Collection of information on fan state." 
        ::= { ruijieDeviceMIBGroups 8 }   

ruijieTemperatureWarningDescGroup OBJECT-GROUP
        OBJECTS { ruijieTemperatureWarningDesc }
        STATUS  current
        DESCRIPTION
                 "Collection of description on temperature change notification." 
        ::= { ruijieDeviceMIBGroups 9 } 

ruijieTemperatureWarningGroup NOTIFICATION-GROUP
	NOTIFICATIONS { ruijieTemperatureWarning }
	STATUS        current
	DESCRIPTION
             "Collection of temperature change notification." 
    ::= { ruijieDeviceMIBGroups 10}
          

-- definitions in RFC 1213 made

        
END
